; AutoCAD 2022 for Windows. APPLOAD this file, type BARBUILD in an empty drawing.
; Generates real 3DSOLID boxes/cylinders at the same coordinates as the DXF.
; Units mm. X left/right; Y rear/front; finished floor Z=0.
; Inner side MFP intersects rear frame 12x50x862 and front upper rail 12x50x70.
; The supplied cut list is retained deliberately; see accompanying message.
(vl-load-com)
(defun bar-layer (doc name col / layers lay)
  (setq layers (vla-get-Layers doc))
  (if (not (tblsearch "LAYER" name)) (vla-Add layers name))
  (setq lay (vla-Item layers name))
  (vla-put-Color lay col))
(defun bar-box (ms layer name x y z dx dy dz col / obj)
  (setq obj (vla-AddBox ms
    (vlax-3d-point (list (+ x (/ dx 2.0)) (+ y (/ dy 2.0)) (+ z (/ dz 2.0))))
    dx dy dz))
  (vla-put-Layer obj layer)
  (if col (vla-put-Color obj col))
  obj)
(defun bar-cyl (ms layer name x y z axis diameter len / obj p p2 ang)
  (setq p (list x y z))
  (setq obj (vla-AddCylinder ms (vlax-3d-point p) (/ diameter 2.0) len))
  (vla-put-Layer obj layer)
  (cond
    ((= axis "+x") (setq p2 (list x (+ y 1.0) z) ang (/ pi 2.0)))
    ((= axis "-x") (setq p2 (list x (+ y 1.0) z) ang (- (/ pi 2.0))))
    ((= axis "+y") (setq p2 (list (+ x 1.0) y z) ang (- (/ pi 2.0))))
    ((= axis "-y") (setq p2 (list (+ x 1.0) y z) ang (/ pi 2.0)))
    ((= axis "-z") (setq p2 (list (+ x 1.0) y z) ang pi)))
  (if p2 (vla-Rotate3D obj (vlax-3d-point p) (vlax-3d-point p2) ang))
  obj)
(defun c:BARBUILD (/ acad doc ms)
  (setq acad (vlax-get-acad-object))
  (setq doc (vla-get-ActiveDocument acad))
  (setq ms (vla-get-ModelSpace doc))
  (if (ssget "_X" (list (cons 8 "BAR-FRAME")))
    (princ "\nBAR-FRAME already has objects. Open a blank drawing before BARBUILD.")
    (progn
      (setvar "INSUNITS" 4)
      (setvar "MEASUREMENT" 1)
      (setvar "LUNITS" 2)
      (setvar "LUPREC" 2)
      (bar-layer doc "BAR-FRAME" 30)
      (bar-layer doc "BAR-COUNTERTOP" 8)
      (bar-layer doc "BAR-WALLS" 253)
      (bar-layer doc "BAR-SLATS" 33)
      (bar-layer doc "BAR-JOINTS-TIMBER-TIMBER" 1)
      (bar-layer doc "BAR-JOINTS-MFP-TIMBER" 4)
      (bar-layer doc "BAR-JOINTS-SLAT-MFP" 3)
      (bar-layer doc "BAR-ANCHORS" 6)
      (bar-box ms "BAR-FRAME" "rear bottom rail 1326" 62 31 0.0 1326 50 70 nil)
      (bar-box ms "BAR-FRAME" "rear top rail 1326" 62 31 792 1326 50 70 nil)
      (bar-box ms "BAR-FRAME" "front upper rail 1326" 62 521 792 1326 50 70 nil)
      (bar-box ms "BAR-FRAME" "rear left vertical 722" 62 31 70 70 50 722 nil)
      (bar-box ms "BAR-FRAME" "rear middle vertical 722" 690 31 70 70 50 722 nil)
      (bar-box ms "BAR-FRAME" "rear right vertical 722" 1318 31 70 70 50 722 nil)
      (bar-box ms "BAR-FRAME" "left side bottom rail 540" 12 31 0.0 50 540 70 nil)
      (bar-box ms "BAR-FRAME" "left side top rail 540" 12 31 792 50 540 70 nil)
      (bar-box ms "BAR-FRAME" "left side rear vertical 722" 12 31 70 50 70 722 nil)
      (bar-box ms "BAR-FRAME" "left side middle vertical 722" 12 266 70 50 70 722 nil)
      (bar-box ms "BAR-FRAME" "left side front vertical 722" 12 501 70 50 70 722 nil)
      (bar-box ms "BAR-FRAME" "right side bottom rail 540" 1388 31 0.0 50 540 70 nil)
      (bar-box ms "BAR-FRAME" "right side top rail 540" 1388 31 792 50 540 70 nil)
      (bar-box ms "BAR-FRAME" "right side rear vertical 722" 1388 31 70 50 70 722 nil)
      (bar-box ms "BAR-FRAME" "right side middle vertical 722" 1388 266 70 50 70 722 nil)
      (bar-box ms "BAR-FRAME" "right side front vertical 722" 1388 501 70 50 70 722 nil)
      (bar-box ms "BAR-COUNTERTOP" "laminated MDF countertop placeholder 1450x600x38" 0.0 0.0 862 1450 600 38 nil)
      (bar-box ms "BAR-WALLS" "rear outer MFP 1426x862" 12 19 0.0 1426 12 862 nil)
      (bar-box ms "BAR-WALLS" "rear inner MFP 1302x862" 74 81 0.0 1302 12 862 nil)
      (bar-box ms "BAR-WALLS" "left outer side MFP 540x862" 0.0 31 0.0 12 540 862 nil)
      (bar-box ms "BAR-WALLS" "left inner side MFP 540x862" 62 31 0.0 12 540 862 nil)
      (bar-box ms "BAR-WALLS" "right inner side MFP 540x862" 1376 31 0.0 12 540 862 nil)
      (bar-box ms "BAR-WALLS" "right outer side MFP 540x862" 1438 31 0.0 12 540 862 nil)
      (bar-box ms "BAR-WALLS" "left front MFP strip 74x862" 0.0 571 0.0 74 12 862 nil)
      (bar-box ms "BAR-WALLS" "right front MFP strip 74x862" 1376 571 0.0 74 12 862 nil)
      (bar-box ms "BAR-SLATS" "outside slat segment 01 / 6 (245x857x19) backing" 12 15 5 245 4 857 250)
      (bar-box ms "BAR-SLATS" "outside slat segment 01 / 6 (245x857x19) raised slat 1" 17 0.0 5 38 15 857 33)
      (bar-box ms "BAR-SLATS" "outside slat segment 01 / 6 (245x857x19) raised slat 2" 66 0.0 5 38 15 857 33)
      (bar-box ms "BAR-SLATS" "outside slat segment 01 / 6 (245x857x19) raised slat 3" 115 0.0 5 38 15 857 33)
      (bar-box ms "BAR-SLATS" "outside slat segment 01 / 6 (245x857x19) raised slat 4" 164 0.0 5 38 15 857 33)
      (bar-box ms "BAR-SLATS" "outside slat segment 01 / 6 (245x857x19) raised slat 5" 213 0.0 5 38 15 857 33)
      (bar-box ms "BAR-SLATS" "outside slat segment 02 / 6 (245x857x19) backing" 257 15 5 245 4 857 250)
      (bar-box ms "BAR-SLATS" "outside slat segment 02 / 6 (245x857x19) raised slat 1" 262 0.0 5 38 15 857 33)
      (bar-box ms "BAR-SLATS" "outside slat segment 02 / 6 (245x857x19) raised slat 2" 311 0.0 5 38 15 857 33)
      (bar-box ms "BAR-SLATS" "outside slat segment 02 / 6 (245x857x19) raised slat 3" 360 0.0 5 38 15 857 33)
      (bar-box ms "BAR-SLATS" "outside slat segment 02 / 6 (245x857x19) raised slat 4" 409 0.0 5 38 15 857 33)
      (bar-box ms "BAR-SLATS" "outside slat segment 02 / 6 (245x857x19) raised slat 5" 458 0.0 5 38 15 857 33)
      (bar-box ms "BAR-SLATS" "outside slat segment 03 / 6 (245x857x19) backing" 502 15 5 245 4 857 250)
      (bar-box ms "BAR-SLATS" "outside slat segment 03 / 6 (245x857x19) raised slat 1" 507 0.0 5 38 15 857 33)
      (bar-box ms "BAR-SLATS" "outside slat segment 03 / 6 (245x857x19) raised slat 2" 556 0.0 5 38 15 857 33)
      (bar-box ms "BAR-SLATS" "outside slat segment 03 / 6 (245x857x19) raised slat 3" 605 0.0 5 38 15 857 33)
      (bar-box ms "BAR-SLATS" "outside slat segment 03 / 6 (245x857x19) raised slat 4" 654 0.0 5 38 15 857 33)
      (bar-box ms "BAR-SLATS" "outside slat segment 03 / 6 (245x857x19) raised slat 5" 703 0.0 5 38 15 857 33)
      (bar-box ms "BAR-SLATS" "outside slat segment 04 / 6 (245x857x19) backing" 747 15 5 245 4 857 250)
      (bar-box ms "BAR-SLATS" "outside slat segment 04 / 6 (245x857x19) raised slat 1" 752 0.0 5 38 15 857 33)
      (bar-box ms "BAR-SLATS" "outside slat segment 04 / 6 (245x857x19) raised slat 2" 801 0.0 5 38 15 857 33)
      (bar-box ms "BAR-SLATS" "outside slat segment 04 / 6 (245x857x19) raised slat 3" 850 0.0 5 38 15 857 33)
      (bar-box ms "BAR-SLATS" "outside slat segment 04 / 6 (245x857x19) raised slat 4" 899 0.0 5 38 15 857 33)
      (bar-box ms "BAR-SLATS" "outside slat segment 04 / 6 (245x857x19) raised slat 5" 948 0.0 5 38 15 857 33)
      (bar-box ms "BAR-SLATS" "outside slat segment 05 / 6 (245x857x19) backing" 992 15 5 245 4 857 250)
      (bar-box ms "BAR-SLATS" "outside slat segment 05 / 6 (245x857x19) raised slat 1" 997 0.0 5 38 15 857 33)
      (bar-box ms "BAR-SLATS" "outside slat segment 05 / 6 (245x857x19) raised slat 2" 1046 0.0 5 38 15 857 33)
      (bar-box ms "BAR-SLATS" "outside slat segment 05 / 6 (245x857x19) raised slat 3" 1095 0.0 5 38 15 857 33)
      (bar-box ms "BAR-SLATS" "outside slat segment 05 / 6 (245x857x19) raised slat 4" 1144 0.0 5 38 15 857 33)
      (bar-box ms "BAR-SLATS" "outside slat segment 05 / 6 (245x857x19) raised slat 5" 1193 0.0 5 38 15 857 33)
      (bar-box ms "BAR-SLATS" "outside slat segment 06 / 6 (201x857x19) backing" 1237 15 5 201 4 857 250)
      (bar-box ms "BAR-SLATS" "outside slat segment 06 / 6 (201x857x19) raised slat 1" 1242 0.0 5 38 15 857 33)
      (bar-box ms "BAR-SLATS" "outside slat segment 06 / 6 (201x857x19) raised slat 2" 1291 0.0 5 38 15 857 33)
      (bar-box ms "BAR-SLATS" "outside slat segment 06 / 6 (201x857x19) raised slat 3" 1340 0.0 5 38 15 857 33)
      (bar-box ms "BAR-SLATS" "outside slat segment 06 / 6 (201x857x19) raised slat 4" 1389 0.0 5 38 15 857 33)
      (bar-box ms "BAR-SLATS" "inside slat segment 01 / 6 (245x857x19) backing" 74 93 5 245 4 857 250)
      (bar-box ms "BAR-SLATS" "inside slat segment 01 / 6 (245x857x19) raised slat 1" 79 97 5 38 15 857 33)
      (bar-box ms "BAR-SLATS" "inside slat segment 01 / 6 (245x857x19) raised slat 2" 128 97 5 38 15 857 33)
      (bar-box ms "BAR-SLATS" "inside slat segment 01 / 6 (245x857x19) raised slat 3" 177 97 5 38 15 857 33)
      (bar-box ms "BAR-SLATS" "inside slat segment 01 / 6 (245x857x19) raised slat 4" 226 97 5 38 15 857 33)
      (bar-box ms "BAR-SLATS" "inside slat segment 01 / 6 (245x857x19) raised slat 5" 275 97 5 38 15 857 33)
      (bar-box ms "BAR-SLATS" "inside slat segment 02 / 6 (245x857x19) backing" 319 93 5 245 4 857 250)
      (bar-box ms "BAR-SLATS" "inside slat segment 02 / 6 (245x857x19) raised slat 1" 324 97 5 38 15 857 33)
      (bar-box ms "BAR-SLATS" "inside slat segment 02 / 6 (245x857x19) raised slat 2" 373 97 5 38 15 857 33)
      (bar-box ms "BAR-SLATS" "inside slat segment 02 / 6 (245x857x19) raised slat 3" 422 97 5 38 15 857 33)
      (bar-box ms "BAR-SLATS" "inside slat segment 02 / 6 (245x857x19) raised slat 4" 471 97 5 38 15 857 33)
      (bar-box ms "BAR-SLATS" "inside slat segment 02 / 6 (245x857x19) raised slat 5" 520 97 5 38 15 857 33)
      (bar-box ms "BAR-SLATS" "inside slat segment 03 / 6 (245x857x19) backing" 564 93 5 245 4 857 250)
      (bar-box ms "BAR-SLATS" "inside slat segment 03 / 6 (245x857x19) raised slat 1" 569 97 5 38 15 857 33)
      (bar-box ms "BAR-SLATS" "inside slat segment 03 / 6 (245x857x19) raised slat 2" 618 97 5 38 15 857 33)
      (bar-box ms "BAR-SLATS" "inside slat segment 03 / 6 (245x857x19) raised slat 3" 667 97 5 38 15 857 33)
      (bar-box ms "BAR-SLATS" "inside slat segment 03 / 6 (245x857x19) raised slat 4" 716 97 5 38 15 857 33)
      (bar-box ms "BAR-SLATS" "inside slat segment 03 / 6 (245x857x19) raised slat 5" 765 97 5 38 15 857 33)
      (bar-box ms "BAR-SLATS" "inside slat segment 04 / 6 (245x857x19) backing" 809 93 5 245 4 857 250)
      (bar-box ms "BAR-SLATS" "inside slat segment 04 / 6 (245x857x19) raised slat 1" 814 97 5 38 15 857 33)
      (bar-box ms "BAR-SLATS" "inside slat segment 04 / 6 (245x857x19) raised slat 2" 863 97 5 38 15 857 33)
      (bar-box ms "BAR-SLATS" "inside slat segment 04 / 6 (245x857x19) raised slat 3" 912 97 5 38 15 857 33)
      (bar-box ms "BAR-SLATS" "inside slat segment 04 / 6 (245x857x19) raised slat 4" 961 97 5 38 15 857 33)
      (bar-box ms "BAR-SLATS" "inside slat segment 04 / 6 (245x857x19) raised slat 5" 1010 97 5 38 15 857 33)
      (bar-box ms "BAR-SLATS" "inside slat segment 05 / 6 (245x857x19) backing" 1054 93 5 245 4 857 250)
      (bar-box ms "BAR-SLATS" "inside slat segment 05 / 6 (245x857x19) raised slat 1" 1059 97 5 38 15 857 33)
      (bar-box ms "BAR-SLATS" "inside slat segment 05 / 6 (245x857x19) raised slat 2" 1108 97 5 38 15 857 33)
      (bar-box ms "BAR-SLATS" "inside slat segment 05 / 6 (245x857x19) raised slat 3" 1157 97 5 38 15 857 33)
      (bar-box ms "BAR-SLATS" "inside slat segment 05 / 6 (245x857x19) raised slat 4" 1206 97 5 38 15 857 33)
      (bar-box ms "BAR-SLATS" "inside slat segment 05 / 6 (245x857x19) raised slat 5" 1255 97 5 38 15 857 33)
      (bar-box ms "BAR-SLATS" "inside slat segment 06 / 6 (77x857x19) backing" 1299 93 5 77 4 857 250)
      (bar-box ms "BAR-SLATS" "inside slat segment 06 / 6 (77x857x19) raised slat 1" 1304 97 5 38 15 857 33)
      (bar-box ms "BAR-SLATS" "inside slat segment 06 / 6 (77x857x19) raised slat 2" 1353 97 5 23 15 857 33)
      (bar-cyl ms "BAR-JOINTS-TIMBER-TIMBER" "rear left bottom joint 6x120" 80 56 60 "+z" 6 120)
      (bar-cyl ms "BAR-JOINTS-TIMBER-TIMBER" "rear left bottom joint 6x120" 114 56 60 "+z" 6 120)
      (bar-cyl ms "BAR-JOINTS-TIMBER-TIMBER" "rear left top joint 6x120" 80 56 802 "+z" 6 120)
      (bar-cyl ms "BAR-JOINTS-TIMBER-TIMBER" "rear left top joint 6x120" 114 56 802 "+z" 6 120)
      (bar-cyl ms "BAR-JOINTS-TIMBER-TIMBER" "rear middle bottom joint 6x120" 708 56 60 "+z" 6 120)
      (bar-cyl ms "BAR-JOINTS-TIMBER-TIMBER" "rear middle bottom joint 6x120" 742 56 60 "+z" 6 120)
      (bar-cyl ms "BAR-JOINTS-TIMBER-TIMBER" "rear middle top joint 6x120" 708 56 802 "+z" 6 120)
      (bar-cyl ms "BAR-JOINTS-TIMBER-TIMBER" "rear middle top joint 6x120" 742 56 802 "+z" 6 120)
      (bar-cyl ms "BAR-JOINTS-TIMBER-TIMBER" "rear right bottom joint 6x120" 1336 56 60 "+z" 6 120)
      (bar-cyl ms "BAR-JOINTS-TIMBER-TIMBER" "rear right bottom joint 6x120" 1370 56 60 "+z" 6 120)
      (bar-cyl ms "BAR-JOINTS-TIMBER-TIMBER" "rear right top joint 6x120" 1336 56 802 "+z" 6 120)
      (bar-cyl ms "BAR-JOINTS-TIMBER-TIMBER" "rear right top joint 6x120" 1370 56 802 "+z" 6 120)
      (bar-cyl ms "BAR-JOINTS-TIMBER-TIMBER" "left rear bottom joint 6x120" 37 49 60 "+z" 6 120)
      (bar-cyl ms "BAR-JOINTS-TIMBER-TIMBER" "left rear bottom joint 6x120" 37 83 60 "+z" 6 120)
      (bar-cyl ms "BAR-JOINTS-TIMBER-TIMBER" "left rear top joint 6x120" 37 49 802 "+z" 6 120)
      (bar-cyl ms "BAR-JOINTS-TIMBER-TIMBER" "left rear top joint 6x120" 37 83 802 "+z" 6 120)
      (bar-cyl ms "BAR-JOINTS-TIMBER-TIMBER" "left middle bottom joint 6x120" 37 284 60 "+z" 6 120)
      (bar-cyl ms "BAR-JOINTS-TIMBER-TIMBER" "left middle bottom joint 6x120" 37 318 60 "+z" 6 120)
      (bar-cyl ms "BAR-JOINTS-TIMBER-TIMBER" "left middle top joint 6x120" 37 284 802 "+z" 6 120)
      (bar-cyl ms "BAR-JOINTS-TIMBER-TIMBER" "left middle top joint 6x120" 37 318 802 "+z" 6 120)
      (bar-cyl ms "BAR-JOINTS-TIMBER-TIMBER" "left front bottom joint 6x120" 37 519 60 "+z" 6 120)
      (bar-cyl ms "BAR-JOINTS-TIMBER-TIMBER" "left front bottom joint 6x120" 37 553 60 "+z" 6 120)
      (bar-cyl ms "BAR-JOINTS-TIMBER-TIMBER" "left front top joint 6x120" 37 519 802 "+z" 6 120)
      (bar-cyl ms "BAR-JOINTS-TIMBER-TIMBER" "left front top joint 6x120" 37 553 802 "+z" 6 120)
      (bar-cyl ms "BAR-JOINTS-TIMBER-TIMBER" "right rear bottom joint 6x120" 1413 49 60 "+z" 6 120)
      (bar-cyl ms "BAR-JOINTS-TIMBER-TIMBER" "right rear bottom joint 6x120" 1413 83 60 "+z" 6 120)
      (bar-cyl ms "BAR-JOINTS-TIMBER-TIMBER" "right rear top joint 6x120" 1413 49 802 "+z" 6 120)
      (bar-cyl ms "BAR-JOINTS-TIMBER-TIMBER" "right rear top joint 6x120" 1413 83 802 "+z" 6 120)
      (bar-cyl ms "BAR-JOINTS-TIMBER-TIMBER" "right middle bottom joint 6x120" 1413 284 60 "+z" 6 120)
      (bar-cyl ms "BAR-JOINTS-TIMBER-TIMBER" "right middle bottom joint 6x120" 1413 318 60 "+z" 6 120)
      (bar-cyl ms "BAR-JOINTS-TIMBER-TIMBER" "right middle top joint 6x120" 1413 284 802 "+z" 6 120)
      (bar-cyl ms "BAR-JOINTS-TIMBER-TIMBER" "right middle top joint 6x120" 1413 318 802 "+z" 6 120)
      (bar-cyl ms "BAR-JOINTS-TIMBER-TIMBER" "right front bottom joint 6x120" 1413 519 60 "+z" 6 120)
      (bar-cyl ms "BAR-JOINTS-TIMBER-TIMBER" "right front bottom joint 6x120" 1413 553 60 "+z" 6 120)
      (bar-cyl ms "BAR-JOINTS-TIMBER-TIMBER" "right front top joint 6x120" 1413 519 802 "+z" 6 120)
      (bar-cyl ms "BAR-JOINTS-TIMBER-TIMBER" "right front top joint 6x120" 1413 553 802 "+z" 6 120)
      (bar-cyl ms "BAR-JOINTS-TIMBER-TIMBER" "rear corner to left side 6x120" 72 43 440 "+x" 6 120)
      (bar-cyl ms "BAR-JOINTS-TIMBER-TIMBER" "rear corner to left side 6x120" 72 70 440 "+x" 6 120)
      (bar-cyl ms "BAR-JOINTS-TIMBER-TIMBER" "front upper rail to left side 6x120" 72 535 827 "+x" 6 120)
      (bar-cyl ms "BAR-JOINTS-TIMBER-TIMBER" "front upper rail to left side 6x120" 72 560 827 "+x" 6 120)
      (bar-cyl ms "BAR-JOINTS-TIMBER-TIMBER" "rear corner to right side 6x120" 1378 43 440 "+x" 6 120)
      (bar-cyl ms "BAR-JOINTS-TIMBER-TIMBER" "rear corner to right side 6x120" 1378 70 440 "+x" 6 120)
      (bar-cyl ms "BAR-JOINTS-TIMBER-TIMBER" "front upper rail to right side 6x120" 1378 535 827 "+x" 6 120)
      (bar-cyl ms "BAR-JOINTS-TIMBER-TIMBER" "front upper rail to right side 6x120" 1378 560 827 "+x" 6 120)
      (bar-cyl ms "BAR-JOINTS-MFP-TIMBER" "outer rear MFP into frame 4x40" 37 39 150 "+y" 4 40)
      (bar-cyl ms "BAR-JOINTS-MFP-TIMBER" "outer rear MFP into frame 4x40" 37 39 330 "+y" 4 40)
      (bar-cyl ms "BAR-JOINTS-MFP-TIMBER" "outer rear MFP into frame 4x40" 37 39 520 "+y" 4 40)
      (bar-cyl ms "BAR-JOINTS-MFP-TIMBER" "outer rear MFP into frame 4x40" 37 39 700 "+y" 4 40)
      (bar-cyl ms "BAR-JOINTS-MFP-TIMBER" "outer rear MFP into frame 4x40" 97 39 150 "+y" 4 40)
      (bar-cyl ms "BAR-JOINTS-MFP-TIMBER" "outer rear MFP into frame 4x40" 97 39 330 "+y" 4 40)
      (bar-cyl ms "BAR-JOINTS-MFP-TIMBER" "outer rear MFP into frame 4x40" 97 39 520 "+y" 4 40)
      (bar-cyl ms "BAR-JOINTS-MFP-TIMBER" "outer rear MFP into frame 4x40" 97 39 700 "+y" 4 40)
      (bar-cyl ms "BAR-JOINTS-MFP-TIMBER" "outer rear MFP into frame 4x40" 725 39 150 "+y" 4 40)
      (bar-cyl ms "BAR-JOINTS-MFP-TIMBER" "outer rear MFP into frame 4x40" 725 39 330 "+y" 4 40)
      (bar-cyl ms "BAR-JOINTS-MFP-TIMBER" "outer rear MFP into frame 4x40" 725 39 520 "+y" 4 40)
      (bar-cyl ms "BAR-JOINTS-MFP-TIMBER" "outer rear MFP into frame 4x40" 725 39 700 "+y" 4 40)
      (bar-cyl ms "BAR-JOINTS-MFP-TIMBER" "outer rear MFP into frame 4x40" 1353 39 150 "+y" 4 40)
      (bar-cyl ms "BAR-JOINTS-MFP-TIMBER" "outer rear MFP into frame 4x40" 1353 39 330 "+y" 4 40)
      (bar-cyl ms "BAR-JOINTS-MFP-TIMBER" "outer rear MFP into frame 4x40" 1353 39 520 "+y" 4 40)
      (bar-cyl ms "BAR-JOINTS-MFP-TIMBER" "outer rear MFP into frame 4x40" 1353 39 700 "+y" 4 40)
      (bar-cyl ms "BAR-JOINTS-MFP-TIMBER" "outer rear MFP into frame 4x40" 1413 39 150 "+y" 4 40)
      (bar-cyl ms "BAR-JOINTS-MFP-TIMBER" "outer rear MFP into frame 4x40" 1413 39 330 "+y" 4 40)
      (bar-cyl ms "BAR-JOINTS-MFP-TIMBER" "outer rear MFP into frame 4x40" 1413 39 520 "+y" 4 40)
      (bar-cyl ms "BAR-JOINTS-MFP-TIMBER" "outer rear MFP into frame 4x40" 1413 39 700 "+y" 4 40)
      (bar-cyl ms "BAR-JOINTS-MFP-TIMBER" "inner rear MFP into frame 4x40" 97 73 100 "+y" 4 40)
      (bar-cyl ms "BAR-JOINTS-MFP-TIMBER" "inner rear MFP into frame 4x40" 97 73 225 "+y" 4 40)
      (bar-cyl ms "BAR-JOINTS-MFP-TIMBER" "inner rear MFP into frame 4x40" 97 73 350 "+y" 4 40)
      (bar-cyl ms "BAR-JOINTS-MFP-TIMBER" "inner rear MFP into frame 4x40" 97 73 475 "+y" 4 40)
      (bar-cyl ms "BAR-JOINTS-MFP-TIMBER" "inner rear MFP into frame 4x40" 97 73 600 "+y" 4 40)
      (bar-cyl ms "BAR-JOINTS-MFP-TIMBER" "inner rear MFP into frame 4x40" 97 73 725 "+y" 4 40)
      (bar-cyl ms "BAR-JOINTS-MFP-TIMBER" "inner rear MFP into frame 4x40" 725 73 100 "+y" 4 40)
      (bar-cyl ms "BAR-JOINTS-MFP-TIMBER" "inner rear MFP into frame 4x40" 725 73 225 "+y" 4 40)
      (bar-cyl ms "BAR-JOINTS-MFP-TIMBER" "inner rear MFP into frame 4x40" 725 73 350 "+y" 4 40)
      (bar-cyl ms "BAR-JOINTS-MFP-TIMBER" "inner rear MFP into frame 4x40" 725 73 475 "+y" 4 40)
      (bar-cyl ms "BAR-JOINTS-MFP-TIMBER" "inner rear MFP into frame 4x40" 725 73 600 "+y" 4 40)
      (bar-cyl ms "BAR-JOINTS-MFP-TIMBER" "inner rear MFP into frame 4x40" 725 73 725 "+y" 4 40)
      (bar-cyl ms "BAR-JOINTS-MFP-TIMBER" "inner rear MFP into frame 4x40" 1353 73 100 "+y" 4 40)
      (bar-cyl ms "BAR-JOINTS-MFP-TIMBER" "inner rear MFP into frame 4x40" 1353 73 225 "+y" 4 40)
      (bar-cyl ms "BAR-JOINTS-MFP-TIMBER" "inner rear MFP into frame 4x40" 1353 73 350 "+y" 4 40)
      (bar-cyl ms "BAR-JOINTS-MFP-TIMBER" "inner rear MFP into frame 4x40" 1353 73 475 "+y" 4 40)
      (bar-cyl ms "BAR-JOINTS-MFP-TIMBER" "inner rear MFP into frame 4x40" 1353 73 600 "+y" 4 40)
      (bar-cyl ms "BAR-JOINTS-MFP-TIMBER" "inner rear MFP into frame 4x40" 1353 73 725 "+y" 4 40)
      (bar-cyl ms "BAR-JOINTS-MFP-TIMBER" "left outer side MFP into frame 4x40" 20 86 150 "+x" 4 40)
      (bar-cyl ms "BAR-JOINTS-MFP-TIMBER" "left outer side MFP into frame 4x40" 20 86 330 "+x" 4 40)
      (bar-cyl ms "BAR-JOINTS-MFP-TIMBER" "left outer side MFP into frame 4x40" 20 86 520 "+x" 4 40)
      (bar-cyl ms "BAR-JOINTS-MFP-TIMBER" "left outer side MFP into frame 4x40" 20 86 700 "+x" 4 40)
      (bar-cyl ms "BAR-JOINTS-MFP-TIMBER" "left outer side MFP into frame 4x40" 20 301 150 "+x" 4 40)
      (bar-cyl ms "BAR-JOINTS-MFP-TIMBER" "left outer side MFP into frame 4x40" 20 301 330 "+x" 4 40)
      (bar-cyl ms "BAR-JOINTS-MFP-TIMBER" "left outer side MFP into frame 4x40" 20 301 520 "+x" 4 40)
      (bar-cyl ms "BAR-JOINTS-MFP-TIMBER" "left outer side MFP into frame 4x40" 20 301 700 "+x" 4 40)
      (bar-cyl ms "BAR-JOINTS-MFP-TIMBER" "left outer side MFP into frame 4x40" 20 536 150 "+x" 4 40)
      (bar-cyl ms "BAR-JOINTS-MFP-TIMBER" "left outer side MFP into frame 4x40" 20 536 330 "+x" 4 40)
      (bar-cyl ms "BAR-JOINTS-MFP-TIMBER" "left outer side MFP into frame 4x40" 20 536 520 "+x" 4 40)
      (bar-cyl ms "BAR-JOINTS-MFP-TIMBER" "left outer side MFP into frame 4x40" 20 536 700 "+x" 4 40)
      (bar-cyl ms "BAR-JOINTS-MFP-TIMBER" "left inner side MFP into frame 4x40" 54 86 150 "+x" 4 40)
      (bar-cyl ms "BAR-JOINTS-MFP-TIMBER" "left inner side MFP into frame 4x40" 54 86 330 "+x" 4 40)
      (bar-cyl ms "BAR-JOINTS-MFP-TIMBER" "left inner side MFP into frame 4x40" 54 86 520 "+x" 4 40)
      (bar-cyl ms "BAR-JOINTS-MFP-TIMBER" "left inner side MFP into frame 4x40" 54 86 700 "+x" 4 40)
      (bar-cyl ms "BAR-JOINTS-MFP-TIMBER" "left inner side MFP into frame 4x40" 54 301 150 "+x" 4 40)
      (bar-cyl ms "BAR-JOINTS-MFP-TIMBER" "left inner side MFP into frame 4x40" 54 301 330 "+x" 4 40)
      (bar-cyl ms "BAR-JOINTS-MFP-TIMBER" "left inner side MFP into frame 4x40" 54 301 520 "+x" 4 40)
      (bar-cyl ms "BAR-JOINTS-MFP-TIMBER" "left inner side MFP into frame 4x40" 54 301 700 "+x" 4 40)
      (bar-cyl ms "BAR-JOINTS-MFP-TIMBER" "left inner side MFP into frame 4x40" 54 536 150 "+x" 4 40)
      (bar-cyl ms "BAR-JOINTS-MFP-TIMBER" "left inner side MFP into frame 4x40" 54 536 330 "+x" 4 40)
      (bar-cyl ms "BAR-JOINTS-MFP-TIMBER" "left inner side MFP into frame 4x40" 54 536 520 "+x" 4 40)
      (bar-cyl ms "BAR-JOINTS-MFP-TIMBER" "left inner side MFP into frame 4x40" 54 536 700 "+x" 4 40)
      (bar-cyl ms "BAR-JOINTS-MFP-TIMBER" "right inner side MFP into frame 4x40" 1396 86 150 "+x" 4 40)
      (bar-cyl ms "BAR-JOINTS-MFP-TIMBER" "right inner side MFP into frame 4x40" 1396 86 330 "+x" 4 40)
      (bar-cyl ms "BAR-JOINTS-MFP-TIMBER" "right inner side MFP into frame 4x40" 1396 86 520 "+x" 4 40)
      (bar-cyl ms "BAR-JOINTS-MFP-TIMBER" "right inner side MFP into frame 4x40" 1396 86 700 "+x" 4 40)
      (bar-cyl ms "BAR-JOINTS-MFP-TIMBER" "right inner side MFP into frame 4x40" 1396 301 150 "+x" 4 40)
      (bar-cyl ms "BAR-JOINTS-MFP-TIMBER" "right inner side MFP into frame 4x40" 1396 301 330 "+x" 4 40)
      (bar-cyl ms "BAR-JOINTS-MFP-TIMBER" "right inner side MFP into frame 4x40" 1396 301 520 "+x" 4 40)
      (bar-cyl ms "BAR-JOINTS-MFP-TIMBER" "right inner side MFP into frame 4x40" 1396 301 700 "+x" 4 40)
      (bar-cyl ms "BAR-JOINTS-MFP-TIMBER" "right inner side MFP into frame 4x40" 1396 536 150 "+x" 4 40)
      (bar-cyl ms "BAR-JOINTS-MFP-TIMBER" "right inner side MFP into frame 4x40" 1396 536 330 "+x" 4 40)
      (bar-cyl ms "BAR-JOINTS-MFP-TIMBER" "right inner side MFP into frame 4x40" 1396 536 520 "+x" 4 40)
      (bar-cyl ms "BAR-JOINTS-MFP-TIMBER" "right inner side MFP into frame 4x40" 1396 536 700 "+x" 4 40)
      (bar-cyl ms "BAR-JOINTS-MFP-TIMBER" "right outer side MFP into frame 4x40" 1430 86 150 "+x" 4 40)
      (bar-cyl ms "BAR-JOINTS-MFP-TIMBER" "right outer side MFP into frame 4x40" 1430 86 330 "+x" 4 40)
      (bar-cyl ms "BAR-JOINTS-MFP-TIMBER" "right outer side MFP into frame 4x40" 1430 86 520 "+x" 4 40)
      (bar-cyl ms "BAR-JOINTS-MFP-TIMBER" "right outer side MFP into frame 4x40" 1430 86 700 "+x" 4 40)
      (bar-cyl ms "BAR-JOINTS-MFP-TIMBER" "right outer side MFP into frame 4x40" 1430 301 150 "+x" 4 40)
      (bar-cyl ms "BAR-JOINTS-MFP-TIMBER" "right outer side MFP into frame 4x40" 1430 301 330 "+x" 4 40)
      (bar-cyl ms "BAR-JOINTS-MFP-TIMBER" "right outer side MFP into frame 4x40" 1430 301 520 "+x" 4 40)
      (bar-cyl ms "BAR-JOINTS-MFP-TIMBER" "right outer side MFP into frame 4x40" 1430 301 700 "+x" 4 40)
      (bar-cyl ms "BAR-JOINTS-MFP-TIMBER" "right outer side MFP into frame 4x40" 1430 536 150 "+x" 4 40)
      (bar-cyl ms "BAR-JOINTS-MFP-TIMBER" "right outer side MFP into frame 4x40" 1430 536 330 "+x" 4 40)
      (bar-cyl ms "BAR-JOINTS-MFP-TIMBER" "right outer side MFP into frame 4x40" 1430 536 520 "+x" 4 40)
      (bar-cyl ms "BAR-JOINTS-MFP-TIMBER" "right outer side MFP into frame 4x40" 1430 536 700 "+x" 4 40)
      (bar-cyl ms "BAR-JOINTS-MFP-TIMBER" "left front cover MFP into frame 4x40" 37 563 120 "+y" 4 40)
      (bar-cyl ms "BAR-JOINTS-MFP-TIMBER" "left front cover MFP into frame 4x40" 37 563 310 "+y" 4 40)
      (bar-cyl ms "BAR-JOINTS-MFP-TIMBER" "left front cover MFP into frame 4x40" 37 563 500 "+y" 4 40)
      (bar-cyl ms "BAR-JOINTS-MFP-TIMBER" "left front cover MFP into frame 4x40" 37 563 690 "+y" 4 40)
      (bar-cyl ms "BAR-JOINTS-MFP-TIMBER" "right front cover MFP into frame 4x40" 1413 563 120 "+y" 4 40)
      (bar-cyl ms "BAR-JOINTS-MFP-TIMBER" "right front cover MFP into frame 4x40" 1413 563 310 "+y" 4 40)
      (bar-cyl ms "BAR-JOINTS-MFP-TIMBER" "right front cover MFP into frame 4x40" 1413 563 500 "+y" 4 40)
      (bar-cyl ms "BAR-JOINTS-MFP-TIMBER" "right front cover MFP into frame 4x40" 1413 563 690 "+y" 4 40)
      (bar-cyl ms "BAR-JOINTS-SLAT-MFP" "outside slat segment 01 / 6 (245x857x19) slat-to-MFP screw 3.5x16" 60.5 23 90 "+y" 3.5 16)
      (bar-cyl ms "BAR-JOINTS-SLAT-MFP" "outside slat segment 01 / 6 (245x857x19) slat-to-MFP screw 3.5x16" 60.5 23 300 "+y" 3.5 16)
      (bar-cyl ms "BAR-JOINTS-SLAT-MFP" "outside slat segment 01 / 6 (245x857x19) slat-to-MFP screw 3.5x16" 60.5 23 510 "+y" 3.5 16)
      (bar-cyl ms "BAR-JOINTS-SLAT-MFP" "outside slat segment 01 / 6 (245x857x19) slat-to-MFP screw 3.5x16" 60.5 23 720 "+y" 3.5 16)
      (bar-cyl ms "BAR-JOINTS-SLAT-MFP" "outside slat segment 02 / 6 (245x857x19) slat-to-MFP screw 3.5x16" 305.5 23 90 "+y" 3.5 16)
      (bar-cyl ms "BAR-JOINTS-SLAT-MFP" "outside slat segment 02 / 6 (245x857x19) slat-to-MFP screw 3.5x16" 305.5 23 300 "+y" 3.5 16)
      (bar-cyl ms "BAR-JOINTS-SLAT-MFP" "outside slat segment 02 / 6 (245x857x19) slat-to-MFP screw 3.5x16" 305.5 23 510 "+y" 3.5 16)
      (bar-cyl ms "BAR-JOINTS-SLAT-MFP" "outside slat segment 02 / 6 (245x857x19) slat-to-MFP screw 3.5x16" 305.5 23 720 "+y" 3.5 16)
      (bar-cyl ms "BAR-JOINTS-SLAT-MFP" "outside slat segment 03 / 6 (245x857x19) slat-to-MFP screw 3.5x16" 550.5 23 90 "+y" 3.5 16)
      (bar-cyl ms "BAR-JOINTS-SLAT-MFP" "outside slat segment 03 / 6 (245x857x19) slat-to-MFP screw 3.5x16" 550.5 23 300 "+y" 3.5 16)
      (bar-cyl ms "BAR-JOINTS-SLAT-MFP" "outside slat segment 03 / 6 (245x857x19) slat-to-MFP screw 3.5x16" 550.5 23 510 "+y" 3.5 16)
      (bar-cyl ms "BAR-JOINTS-SLAT-MFP" "outside slat segment 03 / 6 (245x857x19) slat-to-MFP screw 3.5x16" 550.5 23 720 "+y" 3.5 16)
      (bar-cyl ms "BAR-JOINTS-SLAT-MFP" "outside slat segment 04 / 6 (245x857x19) slat-to-MFP screw 3.5x16" 795.5 23 90 "+y" 3.5 16)
      (bar-cyl ms "BAR-JOINTS-SLAT-MFP" "outside slat segment 04 / 6 (245x857x19) slat-to-MFP screw 3.5x16" 795.5 23 300 "+y" 3.5 16)
      (bar-cyl ms "BAR-JOINTS-SLAT-MFP" "outside slat segment 04 / 6 (245x857x19) slat-to-MFP screw 3.5x16" 795.5 23 510 "+y" 3.5 16)
      (bar-cyl ms "BAR-JOINTS-SLAT-MFP" "outside slat segment 04 / 6 (245x857x19) slat-to-MFP screw 3.5x16" 795.5 23 720 "+y" 3.5 16)
      (bar-cyl ms "BAR-JOINTS-SLAT-MFP" "outside slat segment 05 / 6 (245x857x19) slat-to-MFP screw 3.5x16" 1040.5 23 90 "+y" 3.5 16)
      (bar-cyl ms "BAR-JOINTS-SLAT-MFP" "outside slat segment 05 / 6 (245x857x19) slat-to-MFP screw 3.5x16" 1040.5 23 300 "+y" 3.5 16)
      (bar-cyl ms "BAR-JOINTS-SLAT-MFP" "outside slat segment 05 / 6 (245x857x19) slat-to-MFP screw 3.5x16" 1040.5 23 510 "+y" 3.5 16)
      (bar-cyl ms "BAR-JOINTS-SLAT-MFP" "outside slat segment 05 / 6 (245x857x19) slat-to-MFP screw 3.5x16" 1040.5 23 720 "+y" 3.5 16)
      (bar-cyl ms "BAR-JOINTS-SLAT-MFP" "outside slat segment 06 / 6 (201x857x19) slat-to-MFP screw 3.5x16" 1285.5 23 90 "+y" 3.5 16)
      (bar-cyl ms "BAR-JOINTS-SLAT-MFP" "outside slat segment 06 / 6 (201x857x19) slat-to-MFP screw 3.5x16" 1285.5 23 300 "+y" 3.5 16)
      (bar-cyl ms "BAR-JOINTS-SLAT-MFP" "outside slat segment 06 / 6 (201x857x19) slat-to-MFP screw 3.5x16" 1285.5 23 510 "+y" 3.5 16)
      (bar-cyl ms "BAR-JOINTS-SLAT-MFP" "outside slat segment 06 / 6 (201x857x19) slat-to-MFP screw 3.5x16" 1285.5 23 720 "+y" 3.5 16)
      (bar-cyl ms "BAR-JOINTS-SLAT-MFP" "inside slat segment 01 / 6 (245x857x19) slat-to-MFP screw 3.5x16" 122.5 89 90 "+y" 3.5 16)
      (bar-cyl ms "BAR-JOINTS-SLAT-MFP" "inside slat segment 01 / 6 (245x857x19) slat-to-MFP screw 3.5x16" 122.5 89 300 "+y" 3.5 16)
      (bar-cyl ms "BAR-JOINTS-SLAT-MFP" "inside slat segment 01 / 6 (245x857x19) slat-to-MFP screw 3.5x16" 122.5 89 510 "+y" 3.5 16)
      (bar-cyl ms "BAR-JOINTS-SLAT-MFP" "inside slat segment 01 / 6 (245x857x19) slat-to-MFP screw 3.5x16" 122.5 89 720 "+y" 3.5 16)
      (bar-cyl ms "BAR-JOINTS-SLAT-MFP" "inside slat segment 02 / 6 (245x857x19) slat-to-MFP screw 3.5x16" 367.5 89 90 "+y" 3.5 16)
      (bar-cyl ms "BAR-JOINTS-SLAT-MFP" "inside slat segment 02 / 6 (245x857x19) slat-to-MFP screw 3.5x16" 367.5 89 300 "+y" 3.5 16)
      (bar-cyl ms "BAR-JOINTS-SLAT-MFP" "inside slat segment 02 / 6 (245x857x19) slat-to-MFP screw 3.5x16" 367.5 89 510 "+y" 3.5 16)
      (bar-cyl ms "BAR-JOINTS-SLAT-MFP" "inside slat segment 02 / 6 (245x857x19) slat-to-MFP screw 3.5x16" 367.5 89 720 "+y" 3.5 16)
      (bar-cyl ms "BAR-JOINTS-SLAT-MFP" "inside slat segment 03 / 6 (245x857x19) slat-to-MFP screw 3.5x16" 612.5 89 90 "+y" 3.5 16)
      (bar-cyl ms "BAR-JOINTS-SLAT-MFP" "inside slat segment 03 / 6 (245x857x19) slat-to-MFP screw 3.5x16" 612.5 89 300 "+y" 3.5 16)
      (bar-cyl ms "BAR-JOINTS-SLAT-MFP" "inside slat segment 03 / 6 (245x857x19) slat-to-MFP screw 3.5x16" 612.5 89 510 "+y" 3.5 16)
      (bar-cyl ms "BAR-JOINTS-SLAT-MFP" "inside slat segment 03 / 6 (245x857x19) slat-to-MFP screw 3.5x16" 612.5 89 720 "+y" 3.5 16)
      (bar-cyl ms "BAR-JOINTS-SLAT-MFP" "inside slat segment 04 / 6 (245x857x19) slat-to-MFP screw 3.5x16" 857.5 89 90 "+y" 3.5 16)
      (bar-cyl ms "BAR-JOINTS-SLAT-MFP" "inside slat segment 04 / 6 (245x857x19) slat-to-MFP screw 3.5x16" 857.5 89 300 "+y" 3.5 16)
      (bar-cyl ms "BAR-JOINTS-SLAT-MFP" "inside slat segment 04 / 6 (245x857x19) slat-to-MFP screw 3.5x16" 857.5 89 510 "+y" 3.5 16)
      (bar-cyl ms "BAR-JOINTS-SLAT-MFP" "inside slat segment 04 / 6 (245x857x19) slat-to-MFP screw 3.5x16" 857.5 89 720 "+y" 3.5 16)
      (bar-cyl ms "BAR-JOINTS-SLAT-MFP" "inside slat segment 05 / 6 (245x857x19) slat-to-MFP screw 3.5x16" 1102.5 89 90 "+y" 3.5 16)
      (bar-cyl ms "BAR-JOINTS-SLAT-MFP" "inside slat segment 05 / 6 (245x857x19) slat-to-MFP screw 3.5x16" 1102.5 89 300 "+y" 3.5 16)
      (bar-cyl ms "BAR-JOINTS-SLAT-MFP" "inside slat segment 05 / 6 (245x857x19) slat-to-MFP screw 3.5x16" 1102.5 89 510 "+y" 3.5 16)
      (bar-cyl ms "BAR-JOINTS-SLAT-MFP" "inside slat segment 05 / 6 (245x857x19) slat-to-MFP screw 3.5x16" 1102.5 89 720 "+y" 3.5 16)
      (bar-cyl ms "BAR-JOINTS-SLAT-MFP" "inside slat segment 06 / 6 (77x857x19) slat-to-MFP screw 3.5x16" 1347.5 89 90 "+y" 3.5 16)
      (bar-cyl ms "BAR-JOINTS-SLAT-MFP" "inside slat segment 06 / 6 (77x857x19) slat-to-MFP screw 3.5x16" 1347.5 89 300 "+y" 3.5 16)
      (bar-cyl ms "BAR-JOINTS-SLAT-MFP" "inside slat segment 06 / 6 (77x857x19) slat-to-MFP screw 3.5x16" 1347.5 89 510 "+y" 3.5 16)
      (bar-cyl ms "BAR-JOINTS-SLAT-MFP" "inside slat segment 06 / 6 (77x857x19) slat-to-MFP screw 3.5x16" 1347.5 89 720 "+y" 3.5 16)
      (bar-cyl ms "BAR-ANCHORS" "rear bottom rail anchor 1 10x240" 250 56 -50 "+z" 10 240)
      (bar-cyl ms "BAR-ANCHORS" "rear bottom rail anchor 2 10x240" 725 56 -50 "+z" 10 240)
      (bar-cyl ms "BAR-ANCHORS" "rear bottom rail anchor 3 10x240" 1200 56 -50 "+z" 10 240)
      (bar-cyl ms "BAR-ANCHORS" "left bottom rail anchor 1 10x240" 37 186 -50 "+z" 10 240)
      (bar-cyl ms "BAR-ANCHORS" "left bottom rail anchor 2 10x240" 37 416 -50 "+z" 10 240)
      (bar-cyl ms "BAR-ANCHORS" "right bottom rail anchor 1 10x240" 1413 186 -50 "+z" 10 240)
      (bar-cyl ms "BAR-ANCHORS" "right bottom rail anchor 2 10x240" 1413 416 -50 "+z" 10 240)
      (vla-Regen doc 1)
      (vla-ZoomAll acad)
      (princ "\nKitchen island built as layered 3DSOLIDs; SAVEAS to DWG.")
    )
  )
  (princ)
)
(princ "\nType BARBUILD in a new blank drawing.")
(princ)
